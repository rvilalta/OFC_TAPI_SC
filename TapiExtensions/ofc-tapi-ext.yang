module ofc-tapi-ext {
    namespace "urn:onf:params:xml:ns:yang:OfcTapiExt";
    prefix ofc-tapi-ext;
    import tapi-topology {
        prefix tapi-topology;
    }
    import tapi-common {
        prefix tapi-common;
    }
    organization "OFC SC-449";
    contact "Ricard Vilalta <mailto:ricard.vilalta@cttc.es>, Karthik Sethuraman <mailto:karthik.sethuraman@necam.com>";
    description "none";
    revision 2017-03-20 {
        description "TAPI Extensions";
        reference "TAPI SDK (Snowmass) Project";
    }
    augment "/tapi-common:context/tapi-topology:topology/tapi-topology:node" {
        uses ofc-node-ext;
        description "none";
    }
    /***********************
    * package object-classes
    **********************/ 
        grouping ofc-node-ext {
            list part-info {
                key 'serial-number';
                uses part-info;
                description "none";
            }
            description "none";
        }

    /***********************
    * package diagrams
    **********************/ 
        grouping part-info {
            leaf model-type {
                type string;
                description "none";
            }
            leaf serial-number {
                type string;
                description "none";
            }
            description "none";
        }

}
